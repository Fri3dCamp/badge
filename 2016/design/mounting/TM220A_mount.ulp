#usage "<b>Data generation for mounting machines</b>\n"
       "<p>"
       "Generates config files for smds on the top and bottom layers "
       "wich can be used with TM220A and TM240A pick and place machines. "
       "The x and y coordinates (units: mm) of the SMD elements are calculated "
       "as mean of maximum and mimimum value of the smds origin points. "
       "The calculated value does not necessarily fit with the origin "
       "point of the part in the layout."
       "<p>"
       "The syntax of the output data looks like this:"
       "<p>"
       "<tt>name x-coord y-coord rotation value package</tt>"
       "<p>"
       "<author>Author: support@cadsoft.de edited by Xinort</author>"

// THIS PROGRAM IS PROVIDED AS IS AND WITHOUT WARRANTY OF ANY KIND, EXPRESSED OR IMPLIED

if (board) board(B) {
int line = 1;
  // Get filename

  string fileName = dlgFileSave("Top - Save File", filesetext(B.name, ".csv"), "*.csv");
  if (fileName == "") exit(0);

  output(fileName) {


	printf("%%,Origin,Offset,X,Y,,\n65535,0,0,0,,\n\n%%,Stack,Offset,Stack,X,Y,\n65535,1,0,0,0,\n65535,1,1,0,0,\n65535,1,2,0,0,\n65535,1,3,0,0,\n65535,1,4,0,0,\n65535,1,5,0,0,\n65535,1,6,0,0,\n65535,1,7,0,0,\n65535,1,8,0,0,\n65535,1,9,0,0,\n65535,1,10,0,0,\n65535,1,11,0,0,\n65535,1,12,0,0,\n65535,1,13,0,0,\n65535,1,14,0,0,\n65535,1,15,0,0,\n\n%%,Feeding,Set,Stack,Feed,Rate,\n65535,2,0,18,\n65535,2,1,4,\n65535,2,2,4,\n65535,2,3,4,\n65535,2,4,4,\n65535,2,5,4,\n65535,2,6,4,\n65535,2,7,4,\n65535,2,8,4,\n65535,2,9,4,\n65535,2,10,4,\n65535,2,11,4,\n65535,2,12,4,\n65535,2,13,8,\n65535,2,14,8,\n65535,2,15,8,\n\n\n%%,Jointed,Board,X,Y\n%%65535,3,0,0\n\n%%,Head,Stack,X,Y,R,H,skip,Ref,Comment,\n");


   B.elements(E) {

     int wasSmd,
         xmax =-2147483648,
         xmin = 2147483647,
         ymax = xmax,
         ymin = xmin;
     
     real angle = 0;

      wasSmd = 0;

        E.package.contacts(C) {
          if (C.smd && C.smd.layer == 1) {
           wasSmd = 1;

            if (C.x > xmax) xmax = C.x;
            if (C.y > ymax) ymax = C.y;
            if (C.x < xmin) xmin = C.x;
            if (C.y < ymin) ymin = C.y;
          }
         }

          
      
            if (wasSmd){
	
          
		if(E.angle >= 0 && E.angle < 91)
		angle = -180 + (90-E.angle);		
		
		else if(E.angle > 90 && E.angle < 181)
		angle = 90 + (180-E.angle);

		else if(E.angle > 180 && E.angle < 271)
		angle = 0 + (270-E.angle);

		else if(E.angle > 270 && E.angle < 361)
		angle = -90 + (360-E.angle);

	printf("%d,1,,%.2f,%.2f,%.0f,,0,%s,%s-%s\n",
          line++,u2mm((xmin + xmax)/2), u2mm((ymin + ymax)/2),
         angle, E.name,E.value,E.package.name);
	}
   }
 }

  // Get filename
  fileName = dlgFileSave("Bottom - Save File", filesetext(B.name, ".csv"), "*.csv");
  if (fileName == "") exit(0);

  output(fileName) {

	printf("%%,Origin,Offset,X,Y,,\n65535,0,0,0,,\n\n%%,Stack,Offset,Stack,X,Y,\n65535,1,0,0,0,\n65535,1,1,0,0,\n65535,1,2,0,0,\n65535,1,3,0,0,\n65535,1,4,0,0,\n65535,1,5,0,0,\n65535,1,6,0,0,\n65535,1,7,0,0,\n65535,1,8,0,0,\n65535,1,9,0,0,\n65535,1,10,0,0,\n65535,1,11,0,0,\n65535,1,12,0,0,\n65535,1,13,0,0,\n65535,1,14,0,0,\n65535,1,15,0,0,\n\n%%,Feeding,Set,Stack,Feed,Rate,\n65535,2,0,18,\n65535,2,1,4,\n65535,2,2,4,\n65535,2,3,4,\n65535,2,4,4,\n65535,2,5,4,\n65535,2,6,4,\n65535,2,7,4,\n65535,2,8,4,\n65535,2,9,4,\n65535,2,10,4,\n65535,2,11,4,\n65535,2,12,4,\n65535,2,13,8,\n65535,2,14,8,\n65535,2,15,8,\n\n\n%%,Jointed,Board,X,Y\n%%65535,3,0,0\n\n%%,Head,Stack,X,Y,R,H,skip,Ref,Comment,\n");

   B.elements(E) {

     int wasSmd,
         xmax =-2147483648,
         xmin = 2147483647,
         ymax = xmax,
         ymin = xmin;
         
     real angle = 0;

      wasSmd = 0;

        E.package.contacts(C) {
          if (C.smd && C.smd.layer == 16) {
           wasSmd = 1;

            if (C.x > xmax) xmax = C.x;
            if (C.y > ymax) ymax = C.y;
            if (C.x < xmin) xmin = C.x;
            if (C.y < ymin) ymin = C.y;
          }
         }

          if (wasSmd){
	
          
		if(E.angle >= 0 && E.angle < 91)
		angle = -180 + (90-E.angle);		
		
		else if(E.angle > 90 && E.angle < 181)
		angle = 90 + (180-E.angle);

		else if(E.angle > 180 && E.angle < 271)
		angle = 0 + (270-E.angle);

		else if(E.angle > 270 && E.angle < 361)
		angle = -90 + (360-E.angle);

	printf("%d,1,,%.2f,%.2f,%.0f,,0,%s,%s-%s\n",
          line++,u2mm((xmin + xmax)/2), u2mm((ymin + ymax)/2),
         angle, E.name,E.value,E.package.name);
	}
   }
 }
}

else {
   dlgMessageBox("\n    Start this ULP in a Board    \n");
   exit (0);
}
